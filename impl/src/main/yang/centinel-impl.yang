module centinel-impl {
    yang-version 1;
    namespace "urn:opendaylight:params:xml:ns:yang:centinel:impl";
    prefix "centinel-impl";

    import config { prefix config; revision-date 2013-04-05; }
    import opendaylight-md-sal-binding { prefix md-sal-binding; revision-date 2013-10-28;}

    description
        "Service definition for centinel project";

    revision "2014-12-10" {
        description
            "Initial revision";
    }

    identity centinel {
        base config:module-type;
        config:java-name-prefix Centinel;
    }

    augment "/config:modules/config:module/config:configuration" {
        case centinel {
            when "/config:modules/config:module/config:type = 'centinel'";
            container broker {
                uses config:service-ref {
                    refine type {
                        mandatory true;
                        config:required-identity md-sal-binding:binding-broker-osgi-registry;
                    }
                }
            }
	    container data-broker {
                uses config:service-ref {
                    refine type {
                        mandatory true;
                        config:required-identity md-sal-binding:binding-async-data-broker;
                    }
                }
            }
            container rpc-registry {
                uses config:service-ref {
                    refine type {
                        mandatory true;
                        config:required-identity md-sal-binding:binding-rpc-registry;
                    }
                }
            }
            container notification-service {
                uses config:service-ref {
                    refine type {
                        mandatory true;
                        config:required-identity md-sal-binding:binding-notification-service;
                    }
                }
            }
        }
    }
}
