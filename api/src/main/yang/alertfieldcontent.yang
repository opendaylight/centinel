/*
 * Copyright (c) 2015 Tata Consultancy services and others.  All rights reserved.
 *
 * This program and the accompanying materials are made available under the
 * terms of the Eclipse Public License v1.0 which accompanies this distribution,
 * and is available at http://www.eclipse.org/legal/epl-v10.html
 */
submodule alertfieldcontent {

  belongs-to "alertrule" {
     prefix "alertrule";
   }
   
   
    contact
      "Sumit Kapoor <sumit.kapoor@tcs.com>";
     
    description
      "YANG definition of Centinel Alert Content Data Model.";
      
    grouping alertfieldcontent{
         uses alertrule:basealerts;
        description
            "alert field content";
        leaf alertName {
                    type string;
           
        }
        leaf fieldContentField {
                   type string;
           
        }
        leaf fieldContentCompareToValue {
                    type string;
           
        }
        leaf fieldContentGrace {
                    type int16;
           
        }
        leaf fieldContentBacklog {
                    type int16;
           
        }
    }

   container alertFieldContentRuleRecord
   {
	    
	    list streamAlertFieldContentRuleList
	    {
	        key configID;
	        uses alertfieldcontent;
	    }
   
   }

   rpc set-alert-field-content-rule {
        description "Setting rules for alert";

        input {
            uses alertfieldcontent;
        }
        output {
            uses alertfieldcontent;            
        }
    }
    
    rpc update-alert-field-content-rule { 
        description "Updating rules for alert"; 

        input { 
            uses alertfieldcontent; 
        } 
        output { 
            uses alertfieldcontent;            
        } 
    } 

	rpc delete-alert-field-content-rule { 
        description "Deleting rules for alert"; 

        input { 
            uses alertfieldcontent; 
        } 
        output { 
            uses alertfieldcontent;            
        } 
    } 

}
