/*
 * Copyright (c) 2015 Tata Consultancy services and others.  All rights reserved.
 *
 * This program and the accompanying materials are made available under the
 * terms of the Eclipse Public License v1.0 which accompanies this distribution,
 * and is available at http://www.eclipse.org/legal/epl-v10.html
 */
module eventinput {

    yang-version 1;
    namespace "urn:opendaylight:params:xml:ns:yang:eventinput";
    prefix "eventinput";

    contact
      "Sumit Kapoor <sumit.kapoor@tcs.com>";
     
    description
      "YANG definition of event notification Model.";
      
      revision "2015-01-05" {
        description "Initial revision of event notification model";
    }
    
    import streamhandler { prefix streamhandler; revision-date "2015-01-05";}

    rpc notify-event {
        description "Notify event to Centinel";

        input {
            uses streamhandler:genericEvent;
        }
       
    } 

}
