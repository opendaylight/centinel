/*
 * Copyright (c) 2015 Tata Consultancy services and others.  All rights reserved.
 *
 * This program and the accompanying materials are made available under the
 * terms of the Eclipse Public License v1.0 which accompanies this distribution,
 * and is available at http://www.eclipse.org/legal/epl-v10.html
 */
submodule basealert {

  belongs-to "alertrule" {
     prefix "alertrule";
   }

    include logserviceprovider;
    
    contact
      "Sumit Kapoor <sumit.kapoor@tcs.com>";
     
    description
      "YANG definition of Centinel Base Alert Data Model.";

    typedef  AlertType {
        description
            "Category of types of Alert.";
        type enumeration {
            enum alert-message-count;
            enum alert-field-value;
            enum alert-field-content;
        }
    }
    grouping basealerts {
	uses rule;
        description
            "Attributes for base alert";
	
	leaf alertTypeClassifier {
            description
                "Name of the type of alert.";
            type AlertType;
        }
        leaf streamID {
            description
                "ID of stream.";
            type string;
        }
    }


}
