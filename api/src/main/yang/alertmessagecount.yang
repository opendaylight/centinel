/*
 * Copyright (c) 2015 Tata Consultancy services and others.  All rights reserved.
 *
 * This program and the accompanying materials are made available under the
 * terms of the Eclipse Public License v1.0 which accompanies this distribution,
 * and is available at http://www.eclipse.org/legal/epl-v10.html
 */
submodule alertmessagecount {

  belongs-to "alertrule" {
     prefix "alertrule";
   }

   contact
      "Sumit Kapoor <sumit.kapoor@tcs.com>";
     
    description
      "YANG definition of Centinel Alert Message Count Data Model.";


    grouping alertmessagecount{
        uses alertrule:basealerts;
        description
            "alert message count";
        leaf alertName {
                    type string;
           
        }
        leaf messageCountOperator {
                    type string;
           
        }
        leaf messageCountCount {
                    type int16;
           
        }
        leaf messageCountGrace {
                    type int16;
           
        }
        leaf messageCountBacklog {
                    type int16;
           
        }
    }

   
   container alertMessageCountRuleRecord
   {
	    
	        list streamAlertMessageCountRuleList
	        {
	            key  configID;
	         	uses alertmessagecount;
	        }
   
   }
      
   rpc set-alert-message-count-rule {
        description "Setting rules for alert";

        input {
            uses alertmessagecount;
        }
        output {
            uses alertmessagecount;            
        }
    }
    
    rpc update-alert-message-count-rule { 
        description "Updating rules for alert"; 

        input { 
            uses alertmessagecount; 
        } 
        output { 
            uses alertmessagecount;            
        } 
    } 

   rpc delete-alert-message-count-rule { 
        description "Deleting rules for alert"; 

        input { 
            uses alertmessagecount; 
        } 
        output { 
            uses alertmessagecount;            
        } 
    } 

}
