/*
 * Copyright (c) 2015 Tata Consultancy services and others.  All rights reserved.
 *
 * This program and the accompanying materials are made available under the
 * terms of the Eclipse Public License v1.0 which accompanies this distribution,
 * and is available at http://www.eclipse.org/legal/epl-v10.html
 */
submodule alertfieldvalue{

  belongs-to "alertrule" {
     prefix "alertrule";
   }
   
     contact
      "Sumit Kapoor <sumit.kapoor@tcs.com>";
     
    description
      "YANG definition of Centinel Alert Field Value Data Model.";

    grouping alertfieldvalue{
        uses alertrule:basealerts;
        description
            "alertfieldvalue";
         leaf alertName {
                    type string;
           
        }
         leaf fieldValueField {
                   type string;
           
        }
        leaf fieldValueThreshholdType {
                    type string;
           
        }
        leaf fieldValueType {
                    type string;
           
        }
        leaf fieldValueThreshhold {
                    type int16;
           
        }
        leaf fieldValueGrace {
                    type int16;
           
        }
        leaf fieldValueBacklog {
                    type int16;
           
        }
    }

   container alertFieldValueRuleRecord
   {
	    
	        list streamAlertFieldValueRuleList
	        {
	            key configID;
	         	uses alertfieldvalue;
	        }
   
   }
  
   rpc set-alert-field-value-rule {
        description "Setting rules for alert";

        input {
            uses alertfieldvalue;
        }
        output {
            uses alertfieldvalue;            
        }
    }
    
    rpc update-alert-field-value-rule { 
        description "Updating rules for alert"; 

        input { 
            uses alertfieldvalue; 
        } 
        output { 
            uses alertfieldvalue;            
        } 
    } 

   rpc delete-alert-field-value-rule { 
        description "Deleting rules for alert"; 

        input { 
            uses alertfieldvalue; 
        } 
        output { 
            uses alertfieldvalue;            
        } 
    } 

}
