module centinel {
    yang-version 1;
    namespace "urn:opendaylight:params:xml:ns:yang:centinel";
    prefix "centinel";

    revision "2015-01-05" {
        description "Initial revision of centinel model";
    }
}
