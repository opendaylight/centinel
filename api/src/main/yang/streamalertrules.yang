/*
 * Copyright (c) 2015 Tata Consultancy services and others.  All rights reserved.
 *
 * This program and the accompanying materials are made available under the
 * terms of the Eclipse Public License v1.0 which accompanies this distribution,
 * and is available at http://www.eclipse.org/legal/epl-v10.html
 */
 submodule streamalertrules {

	belongs-to "alertrule" {
    	 prefix "alertrule";
   	}
	
	    contact
      "Sumit Kapoor <sumit.kapoor@tcs.com>";
     
    description
      "YANG definition of Centinel Stream Alert Rule Data Model.";


 include alertmessagecount;
 include alertfieldvalue;
 include alertfieldcontent;


  	rpc get-all-alert-rule {
        description "Setting rules for alert";

        input {
             leaf streamID {
            description
                "ID of stream.";
            type string;
        }
        }
        output {
           	 list streamAlertMessageCountRuleListSorted
	        {
	         	uses alertmessagecount;
	        }  
              	 list streamAlertFieldValueRuleListSorted
	        {
	         	uses alertfieldvalue;
	        }   
	         list streamAlertFieldContentRuleListSorted
	        {
	                uses alertfieldcontent;
	        }
       
        }
    }

}
