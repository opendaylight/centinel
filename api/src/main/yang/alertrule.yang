/*
 * Copyright (c) 2015 Tata Consultancy services and others.  All rights reserved.
 *
 * This program and the accompanying materials are made available under the
 * terms of the Eclipse Public License v1.0 which accompanies this distribution,
 * and is available at http://www.eclipse.org/legal/epl-v10.html
 */
module alertrule {
    yang-version 1;
    namespace "urn:opendaylight:params:xml:ns:yang:alertrule";
    prefix "alertrule";

    revision "2015-01-05" {
        description "Initial revision of alertrule model";
    }
    

     
    import rule {prefix rule; revision-date "2015-01-05";}
    include alertfieldcontent;
    include alertfieldvalue;
    include alertmessagecount;
    include streamalertrules;
           
	    contact
      "Sumit Kapoor <sumit.kapoor@tcs.com>";
        description
            "Category of types of Alert.";
      
         typedef  AlertType {

        type enumeration {
            enum alert-message-count;
            enum alert-field-value;
            enum alert-field-content;
        }
    }
    grouping basealerts {
	uses rule:rule;
        description
            "Attributes for base alert";
	
	leaf alertTypeClassifier {
            description
                "Name of the type of alert.";
            type AlertType;
        }
        leaf streamID {
            description
                "ID of stream.";
            type string;
        }
    }

 



 }
