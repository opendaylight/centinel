module analytics-impl {
    yang-version 1;
    namespace "urn:opendaylight:params:xml:ns:yang:centinel:analytics:impl";
    prefix "analytics-impl";

    import config { prefix config; revision-date 2013-04-05; }
    import opendaylight-md-sal-binding { prefix md-sal-binding; revision-date 2013-10-28;}

    description
        "Service definition for centinel-analytics project";

    revision "2014-12-10" {
        description
            "Initial revision";
    }

    identity analytics{
        base config:module-type;
        config:java-name-prefix AnalyticS;
    }

    augment "/config:modules/config:module/config:configuration" {
        case analytics {
            when "/config:modules/config:module/config:type = 'analytics'";
            container broker {
                uses config:service-ref {
                    refine type {
                        mandatory true;
                        config:required-identity md-sal-binding:binding-broker-osgi-registry;
                    }
                }
            }
            container data-broker {
                uses config:service-ref {
                    refine type {
                        mandatory true;
                        config:required-identity md-sal-binding:binding-async-data-broker;
                    }
                }
            }
            container rpc-registry {
                uses config:service-ref {
                    refine type {
                        mandatory true;
                        config:required-identity md-sal-binding:binding-rpc-registry;
                    }
                }
            }
            container notification-service {
                uses config:service-ref {
                    refine type {
                        mandatory true;
                        config:required-identity md-sal-binding:binding-notification-service;
                    }
                }
            }
        }
    }
}
